submodule network-server-module {
    belongs-to server-module {
        prefix network;
    }

    import "ietf-inet-types" { // From another namespace 
        prefix inet; 
    }
    import "ieee802-types" {
        prefix ieee;
    }

    typedef percentage {
        type uint16 {
            range "0 .. 100";
        }
    }

    typedef oper-state {
        type enumeration {
            enum up;
            enum down;
        }
    }

    typedef vlan {
        type union {
            type ieee:vlanid;
            type enumeration {
                enum null {
                    description "No VLAN";
                }
            }
        }
    }

    grouping physical-address {
        leaf mac-address {
            type ieee:mac-address;
        }

        leaf vlan {
            type vlan;
            default null;
        }
    }

    container network {
        container configuration {
            leaf ip-address {
                type inet:ipv4-address;
            }

            container ethernet {
                uses physical-address {
                    refine vlan {
                        default 1;
                    }
                }
            }

            container protocols {
                leaf-list dns-server {
                    type inet:ipv4-address;
                    ordered-by user;
                    max-elements 4;
                }

                leaf-list ntp-server {
                    type inet:ipv4-address;
                    ordered-by system; // default value
                    max-elements 8;
                }
            }
        }

        container operational {
            leaf interface-load {
                type percentage;
                units percentage;
                config false;
                description "Percentage of Load in the interface";
            }

            leaf interface-state {
                type oper-state;
                config false;
            }
        }
    }
}
