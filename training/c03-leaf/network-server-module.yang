submodule network-server-module {
    belongs-to server-module {
        prefix network;
    }

    import "ietf-inet-types" { // From another namespace 
        prefix inet; 
    }
    import "ieee802-types" {
        prefix ieee;
    }

    container network {
        leaf ip-address {
            type inet:ipv4-address;
        }

        leaf mac-address {
            type ieee:mac-address;
        }
    }
}
