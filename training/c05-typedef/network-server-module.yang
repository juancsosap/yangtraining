submodule network-server-module {
    belongs-to server-module {
        prefix network;
    }

    import "ietf-inet-types" { // From another namespace 
        prefix inet; 
    }
    import "ieee802-types" {
        prefix ieee;
    }

    typedef percentage {
        type uint16 {
            range "0 .. 100";
        }
    }

    typedef oper-state {
        type enumeration {
            enum up;
            enum down;
        }
    }

    container network {
        container configuration {
            leaf ip-address {
                type inet:ipv4-address;
            }

            leaf mac-address {
                type ieee:mac-address;
            }
        }

        container operational {
            leaf interface-load {
                type percentage;
                units percentage;
                config false;
                description "Percentage of Load in the interface";
            }

            leaf interface-state {
                type oper-state;
                config false;
            }
        }
    }
}
